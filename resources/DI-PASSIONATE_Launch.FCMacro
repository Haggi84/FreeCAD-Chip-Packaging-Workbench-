# SPDX-License-Identifier: GPL-3.0-or-later
# GENERATED by core/desktop_shortcut.py — regenerated whenever the desktop
# shortcut is (re)created. Edits here will be overwritten.
"""
Open FreeCAD directly in the Chip-Packaging workbench.

Retries instead of activating once: FreeCAD discovers Mod/ directories on a
timer, so right after the main window appears the workbench may not be
registered yet. A single call would then succeed or fail depending on how
fast the disk is.
"""

import FreeCAD
import FreeCADGui

_WORKBENCH = 'MyWorkbench'
_TICK_MS = 250
_LEFT = [40]


def _activate():
    try:
        if _WORKBENCH in FreeCADGui.listWorkbenches():
            FreeCADGui.activateWorkbench(_WORKBENCH)
            FreeCAD.Console.PrintMessage(
                "[Launcher] Chip-Packaging workbench active.\n")
            return
    except Exception as exc:
        FreeCAD.Console.PrintWarning(f"[Launcher] {exc}\n")

    _LEFT[0] -= 1
    if _LEFT[0] > 0:
        _retry()
    else:
        FreeCAD.Console.PrintWarning(
            "[Launcher] Chip-Packaging workbench did not register in time; "
            "pick it from the workbench dropdown.\n")


def _retry():
    try:
        from PySide6 import QtCore
    except ImportError:
        from PySide2 import QtCore
    QtCore.QTimer.singleShot(_TICK_MS, _activate)


_retry()
